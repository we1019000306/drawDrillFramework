(defun c:drillingTime()
  	(vl-load-com)
	(Setq EXCEL (Vlax-Get-Or-Create-Object "Excel.Application"))
	(Vlax-Put-Property EXCEL 'Visible -1 )
	(setq cells (Vlax-Get excel 'Cells ))
	(setq i 2)
  	(setq XX (Vlax-Get (vlax-variant-value (vlax-get-property cells "item" (+ i 1) 1)) 'Value2))
	(setq TT (= XX nil))
  	(while (= TT nil)
  		(setq XX (Vlax-Get (vlax-variant-value (vlax-get-property cells "item" (+ i 1) 1)) 'Value2))
		(setq TT (= XX nil))
  		(setq SX (Vlax-Get (vlax-variant-value (vlax-get-property cells "item" i 1)) 'Value2))
		(if (= (type SX) 'STR) (setq SX (atof SX)) (setq SX SX))
	  	(setq SX (* SX -5))
		(setq SY (Vlax-Get (vlax-variant-value (vlax-get-property cells "item" i 2)) 'Value2))
  		(if (= (type SY) 'STR) (setq SY (atof SY)) (setq SY SY))
	        (setq SY (* SY 1.25))
	  	(setq SY (- SY 445))
  		(setq SP (list SY SX))
	  	(setq i (+ i 1))
	  	(setq TX (Vlax-Get (vlax-variant-value (vlax-get-property cells "item" i 1)) 'Value2))
  		(if (= (type TX) 'STR) (setq TX (atof TX)) (setq TX TX))
	  	(setq TX (* TX -5))
  		(setq TY (Vlax-Get (vlax-variant-value (vlax-get-property cells "item" i 2)) 'Value2))
  		(if (= (type TY) 'STR) (setq TY (atof TY)) (setq TY TY))
	        (setq TY (* TY 1.25))
	  	(setq TY (- TY 445))
  		(setq TP (list TY TX))
  		(command "pline" SP TP "")
	  	(print SP)
	  	(print TP)
	 )
)
